V2X-Pcapng-Radio
{ iso(1) identified-organization(3) v2x-pcapng-profile(99999) radio(2) version1(1) }
DEFINITIONS AUTOMATIC TAGS ::= BEGIN
IMPORTS Microseconds, Availability, OpaqueData, V2XTechnology, RegionalExtension, ManufacturerExtension FROM V2X-Pcapng-Common;

-- Exactly one technology branch is selected for each record. DSRC native bytes remain Radiotap followed by IEEE 802.11/WAVE bytes.
TechnologySpecificMetadata ::= CHOICE {
  dsrc     DsrcMetadata,
  arib760  Arib760Metadata,
  lteV2x   LteV2xMetadata,
  nrV2x    NrV2xMetadata,
  other    OpaqueData
}
DsrcMetadata ::= SEQUENCE {
  nativeEncapsulation     DsrcNativeEncapsulation, -- radiotap80211Wave means EPB packet data begins with Radiotap
  regionalExtensions      SEQUENCE OF RegionalExtension OPTIONAL,
  manufacturerExtensions  SEQUENCE OF ManufacturerExtension OPTIONAL,
  ...
}
DsrcNativeEncapsulation ::= ENUMERATED { radiotap80211Wave(0), other(254), unknown(255) }

Arib760Metadata ::= SEQUENCE {
  channelInfo              OpaqueData OPTIONAL,
  phyMacInfo               OpaqueData OPTIONAL,
  regionalExtensions       SEQUENCE OF RegionalExtension OPTIONAL,
  manufacturerExtensions   SEQUENCE OF ManufacturerExtension OPTIONAL,
  ...
}

LteV2xMetadata ::= SEQUENCE {
  sci1                     OpaqueData OPTIONAL,
  packetTransmission       PacketTransmissionSummary OPTIONAL,
  regionalExtensions       SEQUENCE OF RegionalExtension OPTIONAL,
  manufacturerExtensions   SEQUENCE OF ManufacturerExtension OPTIONAL,
  ...
}
NrV2xMetadata ::= SEQUENCE {
  firstStageSci            OpaqueData OPTIONAL,
  secondStageSci           OpaqueData OPTIONAL,
  packetTransmission       PacketTransmissionSummary OPTIONAL,
  regionalExtensions       SEQUENCE OF RegionalExtension OPTIONAL,
  manufacturerExtensions   SEQUENCE OF ManufacturerExtension OPTIONAL,
  ...
}

-- One logical V2X packet may summarize multiple exposed TBs, segments, and HARQ transmissions.
PacketTransmissionSummary ::= SEQUENCE {
  harqUsed                 Availability OPTIONAL,
  transportBlocks          SEQUENCE OF TransportBlockObservation OPTIONAL,
  ...
}
TransportBlockObservation ::= SEQUENCE {
  transportBlockIndex      INTEGER (0..65535),
  segmentCount             INTEGER (0..65535) OPTIONAL,
  harqTransmissions        SEQUENCE OF HarqTransmission OPTIONAL,
  availability             Availability DEFAULT observed,
  ...
}
HarqTransmission ::= SEQUENCE {
  transmissionIndex        INTEGER (0..255),
  timingMicroseconds       Microseconds OPTIONAL,
  controlInfo              OpaqueData OPTIONAL, -- SCI/control snapshot if separately exposed
  availability             Availability DEFAULT observed,
  ...
}
END
