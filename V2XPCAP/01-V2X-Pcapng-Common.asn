V2X-Pcapng-Common
{ iso(1) identified-organization(3) v2x-pcapng-profile(99999) common(1) version1(1) }
DEFINITIONS AUTOMATIC TAGS ::= BEGIN

-- Open V2X Packet-Capture Metadata Profile: common types.
-- Encodings in this profile use a one-microsecond tick for all absolute and duration time values.

RecordId ::= INTEGER (0..18446744073709551615)
InterfaceId ::= INTEGER (0..4294967295)
Microseconds ::= INTEGER (0..18446744073709551615)
SignedMicroseconds ::= INTEGER (-9223372036854775808..9223372036854775807)
Centimeters ::= INTEGER (-2147483648..2147483647)
CentimetersUnsigned ::= INTEGER (0..4294967295)
NanosecondsUnsigned ::= INTEGER (0..4294967295)
OpaqueData ::= OCTET STRING

V2XTechnology ::= ENUMERATED {
  ieee80211pDsrc(0), arib760ItsConnect(1), lteV2x(2), nrV2x(3), other(254), unknown(255)
}
Direction ::= ENUMERATED { receive(0), transmit(1), monitor(2), replay(3), unknown(255) }
Availability ::= ENUMERATED {
  observed(0), derived(1), estimated(2), notAvailable(3), notExposed(4), notApplicable(5), unknown(255)
}
ProcessingResult ::= ENUMERATED {
  notAttempted(0), notProcessed(1), passed(2), failed(3), inconclusive(4), unavailable(5), notApplicable(6), unknown(255)
}

V2XCommonMetadata ::= SEQUENCE {
  profileVersion          INTEGER (1..255),
  recordId                RecordId,
  technology              V2XTechnology,
  direction               Direction,
  observer                ObserverProvenance OPTIONAL,
  receiveObservation      ReceiveObservation OPTIONAL,
  addressing              PayloadAddressing OPTIONAL,
  regionalExtensions      SEQUENCE OF RegionalExtension OPTIONAL,
  manufacturerExtensions  SEQUENCE OF ManufacturerExtension OPTIONAL,
  ...
}

ObserverProvenance ::= SEQUENCE {
  observerId              OCTET STRING OPTIONAL,
  interfaceId             InterfaceId OPTIONAL,
  captureSource           CaptureSource OPTIONAL,
  hardwareIdentifier      UTF8String OPTIONAL,
  softwareVersion         UTF8String OPTIONAL,
  captureAgentVersion     UTF8String OPTIONAL,
  processingAgent         UTF8String OPTIONAL,
  ...
}
CaptureSource ::= ENUMERATED { overTheAir(0), modemExport(1), driverExport(2), replay(3), injected(4), derived(5), unknown(255) }

ReceiveObservation ::= SEQUENCE {
  receiveTime             ReceiveTime OPTIONAL,
  receiverLocation        ReceiverLocation OPTIONAL,
  radioObservation        CommonRadioObservation OPTIONAL,
  ...
}
ReceiveTime ::= SEQUENCE {
  timestampMicroseconds   Microseconds,
  timeEpoch               TimeEpoch,
  timeSynchronization     TimeSynchronization OPTIONAL,
  ...
}
TimeEpoch ::= ENUMERATED { utc(0), gps(1), tai(2), other(254), unknown(255) }
TimeSynchronization ::= SEQUENCE {
  source                  TimeSyncSource,
  state                   TimeSyncState,
  uncertaintyMicroseconds Microseconds OPTIONAL,
  uncertaintyBasis        UncertaintyBasis OPTIONAL,
  leapSecondStatus        LeapSecondStatus OPTIONAL,
  utcOffsetSeconds        INTEGER (-128..127) OPTIONAL,
  holdoverAgeMicroseconds Microseconds OPTIONAL,
  ...
}
TimeSyncSource ::= ENUMERATED { ntp(0), gptp(1), wwan(2), gnss(3), gnss1pps(4), localOscillator(5), other(254), unknown(255) }
TimeSyncState ::= ENUMERATED { locked(0), synchronizing(1), holdover(2), degraded(3), freeRunning(4), unknown(255) }
UncertaintyBasis ::= ENUMERATED { bound(0), oneSigma(1), twoSigma(2), confidenceInterval(3), estimate(4), unknown(255) }
LeapSecondStatus ::= ENUMERATED { current(0), pendingInsertion(1), pendingDeletion(2), unknown(255) }

ReceiverLocation ::= SEQUENCE {
  position                Position3D,
  horizontalErrorCm       CentimetersUnsigned OPTIONAL, -- HEPE
  locationSource          LocationSource OPTIONAL,
  locationAgeMicroseconds Microseconds OPTIONAL,
  ...
}
Position3D ::= CHOICE { geodetic GeodeticPosition, ecef EcefPosition }
GeodeticPosition ::= SEQUENCE { latitude1e7 INTEGER (-900000000..900000000), longitude1e7 INTEGER (-1800000000..1800000000), altitudeCm Centimeters OPTIONAL, ... }
EcefPosition ::= SEQUENCE { xCm Centimeters, yCm Centimeters, zCm Centimeters, ... }
LocationSource ::= ENUMERATED { gnss(0), fused(1), mapMatched(2), manual(3), unknown(255) }

CommonRadioObservation ::= SEQUENCE {
  antennaRssi             SEQUENCE OF AntennaRssi OPTIONAL,
  channelBusy             ChannelBusy OPTIONAL,
  propagationDelay        PropagationDelay OPTIONAL,
  channel                 ChannelDescription OPTIONAL,
  ...
}
AntennaRssi ::= SEQUENCE { antennaId INTEGER (0..255), rssiDbmTenth INTEGER (-2000..1000), availability Availability DEFAULT observed, ... }
ChannelBusy ::= SEQUENCE { busyPercentTenth INTEGER (0..1000), measurementWindowMicroseconds Microseconds OPTIONAL, availability Availability DEFAULT observed, ... }
PropagationDelay ::= SEQUENCE { estimateNanoseconds NanosecondsUnsigned, availability Availability DEFAULT estimated, ... }
ChannelDescription ::= SEQUENCE { centerFrequencyKHz INTEGER (0..100000000), bandwidthKHz INTEGER (0..1000000) OPTIONAL, channelNumber INTEGER (0..65535) OPTIONAL, ... }

PayloadAddressing ::= SEQUENCE {
  payloadKind             PayloadKind,
  sourceL2Id              OCTET STRING OPTIONAL,
  destinationL2Id         OCTET STRING OPTIONAL,
  nonIpFamilyId           OCTET STRING OPTIONAL, -- present for non-IP payload when known
  serviceId               OCTET STRING OPTIONAL,
  ...
}
PayloadKind ::= ENUMERATED { ip(0), nonIp(1), unknown(255) }

RegionalExtension ::= SEQUENCE { regionId UTF8String, extensionId INTEGER (0..65535), value OpaqueData, ... }
ManufacturerExtension ::= SEQUENCE { manufacturerId UTF8String, extensionId INTEGER (0..65535), value OpaqueData, ... }
END
