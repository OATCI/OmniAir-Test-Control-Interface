V2X-Pcapng-Annotations
{ iso(1) identified-organization(3) v2x-pcapng-profile(99999) annotations(4) version1(1) }
DEFINITIONS AUTOMATIC TAGS ::= BEGIN
IMPORTS ProcessingResult, RegionalExtension, ManufacturerExtension FROM V2X-Pcapng-Common
        SecurityValidationAnnotation FROM V2X-Pcapng-Security;

AnalysisAnnotations ::= SEQUENCE {
  securityValidation       SecurityValidationAnnotation OPTIONAL,
  misbehaviorDetection     MbdAnnotation OPTIONAL,
  applicationCongestion    ApplicationCongestionAnnotation OPTIONAL,
  regionalExtensions       SEQUENCE OF RegionalExtension OPTIONAL,
  manufacturerExtensions   SEQUENCE OF ManufacturerExtension OPTIONAL,
  ...
}
MbdAnnotation ::= SEQUENCE {
  attempted                BOOLEAN,
  processed                BOOLEAN,
  result                   ProcessingResult,
  regionalExtensions       SEQUENCE OF RegionalExtension OPTIONAL,
  manufacturerExtensions   SEQUENCE OF ManufacturerExtension OPTIONAL,
  ...
}
ApplicationCongestionAnnotation ::= SEQUENCE {
  attempted                BOOLEAN OPTIONAL,
  processed                BOOLEAN OPTIONAL,
  cqi                      INTEGER (0..255) OPTIONAL,
  vehicleDensityInRange    INTEGER (0..65535) OPTIONAL,
  uniqueRemoteVehiclesSeen INTEGER (0..65535) OPTIONAL,
  measurementWindowMicroseconds INTEGER (0..18446744073709551615) OPTIONAL,
  regionalExtensions       SEQUENCE OF RegionalExtension OPTIONAL,
  manufacturerExtensions   SEQUENCE OF ManufacturerExtension OPTIONAL,
  ...
}
END
