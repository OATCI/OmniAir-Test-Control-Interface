-- OmniTap delayed supplemental results.
-- Normative: Use this object only for data that becomes available after the target EPB has been written. Readers SHALL
-- associate it with the EPB whose epb_packetid equals (sessionTag(sessionId) * 2^32) + recordId, where
-- sessionTag(sessionId) is the last four octets of sessionId as an unsigned big-endian integer. When the file holds
-- Capture Context for more than one session, readers SHALL also confirm that the EPB's session has this full sessionId.
-- Association SHALL NOT use block order, EPB ordinal, or Wireshark frame number. A result with no matching EPB SHALL be
-- reported as unassociated; readers SHALL NOT guess a packet for it and SHALL NOT fail because of it.
-- Normative: Duplicates. Tools can leave two copies of the same result in one file; editcap -d removes duplicate EPBs
-- but not duplicate Custom Blocks. Results from one producer with the same (sessionId, recordId, resultSequence) and
-- byte-for-byte identical Custom Block payloads are one result. If such payloads differ, readers SHALL NOT choose
-- between them and SHALL report the packet as having conflicting results from that producer.
-- Normative: Every OmniTap object identifies its own packet, so a result can be selected, filtered and exported with the
-- packet it describes. A reference dissector SHALL publish the packet identifier of each result as a display-filter
-- field; see 00-OmniTap-Requirements.md.
-- Normative: Several results MAY target the same packet. Results are grouped by producer (pen, productName). Within one
-- producer, the result with the highest resultSequence supersedes that producer's lower-numbered results for the same
-- packet. Results from different producers SHALL be retained side by side; a reader SHALL NOT let one producer's
-- result replace another's.
-- Normative: Absent versus unavailable. An absent OPTIONAL annotation makes no assertion: the producer does not say
-- whether that processing was attempted. ProcessingResult unavailable states that the producer attempted the
-- processing but could not perform it or could not complete it (for example, no verification key store); it is a
-- positive statement about the attempt, not about the packet.
OmniTap-Supplemental-Result { 1 3 6 1 4 1 32473 omniTap(1) supplementalResult(30) major-version-1(1) minor-version-0(0) }
DEFINITIONS AUTOMATIC TAGS ::= BEGIN
EXPORTS ALL;
IMPORTS

   CaptureSessionId,
   RecordId
      FROM OmniTap-Common

   OptionalExtensions
      FROM OmniTap-Extensions
;


-- =============================================================================
-- Supplemental-result envelope.
-- =============================================================================


-- Identifies a target packet and carries one producer's delayed analysis revision.
--
OmniTapSupplementalResult ::= SEQUENCE {

   -- Normative: Capture session that owns the target packet. Its last four octets form the high 32 bits of the
   -- target EPB's epb_packetid. Association key with recordId.
   --
   sessionId            CaptureSessionId,


   -- Normative: Low 32 bits of the target EPB's epb_packetid; equals the recordId in that packet's
   -- OmniTapPacketMetadata, if any. Association key with sessionId.
   --
   recordId             RecordId,


   producer             ResultProducer,                   -- Tool or device that produced this result.


   -- Normative: Per-producer revision number for results about this packet. A producer SHALL give a revised
   -- result a higher value than any earlier result it wrote for the same packet.
   --
   resultSequence       INTEGER (0..65535),


   analysis             AnalysisAnnotations   OPTIONAL,   -- Late analysis annotations applicable to the target packet.

   optionalExtensions   OptionalExtensions    OPTIONAL,   -- Optional regional or third-party annotations for the target packet.

   ...
}

-- Normative: Identity of the tool or device that produced a result. (pen, productName) identifies the producer for the
-- supersession rule above; a producer SHALL use the same pair for all results it writes in one capture session.
ResultProducer ::= SEQUENCE {

   -- IANA Private Enterprise Number of the organization responsible for the producing product.
   --
   pen                       INTEGER (0..4294967295),


   productName               UTF8String (SIZE(1..64)),              -- Product or tool name, unique within that organization.

   producerSoftwareVersion   UTF8String (SIZE(1..32))   OPTIONAL,   -- Product software version that produced the result.

   ...
}


-- Collects the analysis outcomes that are available for one target packet.
--
AnalysisAnnotations ::= SEQUENCE {
   securityValidation               SecurityValidationAnnotation      OPTIONAL,   -- Security-analysis result.

   relevance                        RelevanceAnnotation               OPTIONAL,   -- Relevance-analysis result.

   consistency                      ConsistencyAnnotation             OPTIONAL,   -- Consistency-analysis result.


   -- Misbehavior-detection analysis result.
   --
   misbehaviorDetectionAnnotation   MisbehaviorDetectionAnnotation    OPTIONAL,


   -- Application-level congestion analysis result.
   --
   applicationCongestion            ApplicationCongestionAnnotation   OPTIONAL,

   ...
}


-- =============================================================================
-- Security-validation definitions.
-- =============================================================================


-- Describes the security-validation outcome and optional IEEE 1609.2 details.
--
SecurityValidationAnnotation ::= SEQUENCE {
   status                      ProcessingStatus,   -- Security-validation outcome for the target packet.


   -- IEEE 1609.2 verification result. When status is passed this SHALL be success; when status is failed it SHALL
   -- be the first failing result reported by the verifier.
   --
   ieee1609Dot2Result          Ieee1609Dot2VerificationResult   OPTIONAL,


   -- IEEE 1609.2 Unrecognized Id. Present only when ieee1609Dot2Result is parsingCertificateNotFound,
   -- chainNotEnoughInformationToConstructChain, or chainEndedAtUntrustedRoot.
   --
   unrecognizedCertificateId   HashedId8                        OPTIONAL,

   ...
}


-- =============================================================================
-- Shared processing-status definitions.
-- =============================================================================


-- Describes the outcome of an attempted processing operation.
--
ProcessingStatus ::= SEQUENCE {
   result   ProcessingResult,   -- Outcome of the named processing operation.

   ...
}

ProcessingResult ::= ENUMERATED {
   passed         (0),   -- Processing completed and every applicable check passed.

   failed         (1),   -- Processing completed and one or more applicable checks failed.


   -- Processing completed but could not decide; for example, the signing certificate was not yet available. A
   -- later result from the same producer with a higher resultSequence may replace it.
   --
   inconclusive   (2),


   -- The producer attempted the processing but could not perform or complete it. See the module header for the
   -- difference between unavailable and an absent annotation.
   --
   unavailable    (3),

   ...
}

-- Normative: Result Code of the IEEE Std 1609.2-2025 Sec-SignedDataVerification.confirm primitive. Names and order follow
-- that standard. IEEE Std 1609.2-2025 names these results but does not assign numbers or an ASN.1 type; the numbers below
-- are assigned by OmniTap in the standard's order. If a later published edition assigns numbers, this type SHALL be
-- aligned to them in a compatibility-controlled OmniTap release.
Ieee1609Dot2VerificationResult ::= ENUMERATED {
   success                                              (0),    -- Success.

   inconsistentInputParameters                          (1),    -- Inconsistent input parameters.

   parsingInvalidInput                                  (2),    -- SPDU-Parsing: Invalid Input.

   parsingUnsupportedCriticalInformationField           (3),    -- SPDU-Parsing: Unsupported critical information field.

   parsingCertificateNotFound                           (4),    -- SPDU-Parsing: Certificate not found.

   parsingGenerationTimeNotAvailable                    (5),    -- SPDU-Parsing: Generation time not available.

   parsingLocationNotAvailable                          (6),    -- SPDU-Parsing: Location not available.

   -- SPDU-Certificate-Chain: Not enough information to construct chain.
   --
   chainNotEnoughInformationToConstructChain            (7),

   chainEndedAtUntrustedRoot                            (8),    -- SPDU-Certificate-Chain: Chain ended at untrusted root.

   chainTooLongForImplementation                        (9),    -- SPDU-Certificate-Chain: Chain was too long for implementation.

   chainCertificateRevoked                              (10),   -- SPDU-Certificate-Chain: Certificate revoked.

   chainOverdueCrl                                      (11),   -- SPDU-Certificate-Chain: Overdue CRL.

   chainInconsistentExpiryTimes                         (12),   -- SPDU-Certificate-Chain: Inconsistent expiry times.

   chainInconsistentStartTimes                          (13),   -- SPDU-Certificate-Chain: Inconsistent start times.

   chainInconsistentChainPermissions                    (14),   -- SPDU-Certificate-Chain: Inconsistent chain permissions.

   chainInconsistentValidityRegion                      (15),   -- SPDU-Certificate-Chain: Inconsistent validity region.

   cryptoVerificationFailure                            (16),   -- SPDU-Crypto: Verification failure.

   consistencyFutureCertificateAtGenerationTime         (17),   -- SPDU-Consistency: Future certificate at generation time.

   consistencyExpiredCertificateAtGenerationTime        (18),   -- SPDU-Consistency: Expired certificate at generation time.

   consistencyExpiryDateTooEarly                        (19),   -- SPDU-Consistency: Expiry date too early.

   consistencyExpiryDateTooLate                         (20),   -- SPDU-Consistency: Expiry date too late.

   consistencyFutureDataEndTimeAfterCertificateExpiry   (21),   -- SPDU-Consistency: Future data end time after cert expiry.

   consistencyRelevanceLocationOutsideValidityRegion    (22),   -- SPDU-Consistency: Relevance location outside validity region.

   consistencyNoLocation                                (23),   -- SPDU-Consistency: No location.

   consistencyUnauthorizedPsid                          (24),   -- SPDU-Consistency: Unauthorized PSID.

   consistencyUnauthorizedPsidForAssertedData           (25),   -- SPDU-Consistency: Unauthorized PSID for asserted data.

   internalExpiryTimeBeforeGenerationTime               (26),   -- SPDU-Internal-Consistency: Expiry time before generation time.

   internalExtDataHashDoesNotMatch                      (27),   -- SPDU-Internal-Consistency: extDataHash doesn't match.

   internalNoExtDataHashProvided                        (28),   -- SPDU-Internal-Consistency: no extDataHash provided.

   internalNoExtDataHashPresent                         (29),   -- SPDU-Internal-Consistency: no extDataHash present.

   internalNoOmittedDataHashProvided                    (30),   -- SPDU-Internal-Consistency: no omitted data hash provided.

   internalIncorrectOmittedDataHashLength               (31),   -- SPDU-Internal-Consistency: incorrect omitted data hash length.

   internalNoOmittedDataIndicator                       (32),   -- SPDU-Internal-Consistency: no omitted data indicator.

   localPsidsDoNotMatch                                 (33),   -- SPDU-Local-Consistency: PSIDs don't match.

   localChainTooLongForSdee                             (34),   -- SPDU-Local-Consistency: Chain was too long for SDEE.

   relevanceGenerationTimeTooFarInPast                  (35),   -- SPDU-Relevance: Generation Time too far in past.

   relevanceGenerationTimeTooFarInFuture                (36),   -- SPDU-Relevance: Generation Time too far in future.

   relevanceExpiryTimeInPast                            (37),   -- SPDU-Relevance: Expiry Time in past.

   relevanceLocationTooDistant                          (38),   -- SPDU-Relevance: Location too distant.

   relevanceReplayedSpdu                                (39),   -- SPDU-Relevance: Replayed SPDU.

   relevanceCertificateExpired                          (40),   -- SPDU-Relevance: Certificate expired.

   ...
}

-- Normative: IEEE 1609.2 HashedId8 (the low-order eight octets of a certificate hash). Same definition as HashedId8 in
-- Ieee1609Dot2BaseTypes.
HashedId8 ::= OCTET STRING (SIZE(8))


-- =============================================================================
-- Relevance- and consistency-analysis definitions.
-- =============================================================================


-- Describes the relevance-analysis outcome for a target packet.
--
RelevanceAnnotation ::= SEQUENCE {
   status   ProcessingStatus,   -- Relevance-analysis outcome for the target packet.

   ...
}


-- Describes the consistency-analysis outcome for a target packet.
--
ConsistencyAnnotation ::= SEQUENCE {
   status   ProcessingStatus,   -- Consistency-analysis outcome for the target packet.

   ...
}


-- =============================================================================
-- Misbehavior-detection definitions.
-- =============================================================================


-- Describes the misbehavior-detection outcome and any resulting report material.
--
MisbehaviorDetectionAnnotation ::= SEQUENCE {
   status         ProcessingStatus,   -- Misbehavior-detection outcome for the target packet.


   -- Observations that the detector found for the target packet. Present only when status is failed.
   --
   observations   SEQUENCE (SIZE(1..32)) OF MisbehaviorObservationId   OPTIONAL,


   -- Complete misbehavior report as produced for the Misbehavior Authority: the encoding of SaeJ3287Data (SAE
   -- J3287), retained verbatim. OmniTap does not decode it.
   --
   j3287Report    OCTET STRING (SIZE(1..65535))                        OPTIONAL,

   ...
}

-- Normative: One misbehavior observation as identified by ETSI TS 103 759 v2.1.1 or later and SAE J3287. The triple
-- (reportPsid, targetId, observationId) selects one entry of those standards' observation sets; observationId values
-- restart in each target class, so all three are required.
MisbehaviorObservationId ::= SEQUENCE {

   -- PSID of the observed application (AidSpecificReport aid): 32 BSM (SAE J3287), 36 CAM, 37 DENM, 270549119
   -- application-agnostic (ETSI TS 103 759).
   --
   reportPsid      Psid,


   -- Target class (IdBsmTgt, IdCamTgt, or IdDenmTgt value); e.g. BSM: 2 security, 5 longitudinal acceleration.
   --
   targetId        INTEGER (0..255),


   -- Observation within that target class (IdMbObs value); e.g. BSM security 1..7, BSM longitudinal
   -- acceleration 4 (LongAcc-ValueTooLarge).
   --
   observationId   INTEGER (0..255),

   ...
}

-- Normative: IEEE 1609.2 Provider Service Identifier. Same value set as Psid in Ieee1609Dot2BaseTypes; restated here
-- so that OmniTap does not import the IEEE 1609.2 modules.
Psid ::= INTEGER (0..MAX)


-- =============================================================================
-- Application-congestion definitions.
-- =============================================================================


-- Describes application-level channel quality and vehicle-density measurements.
--
ApplicationCongestionAnnotation ::= SEQUENCE {

   -- SAE J3161 channel-quality indicator normalized to a 0..10000 scale.
   --
   j3161ChannelQualityIndicatorX10000   INTEGER (0..10000)   OPTIONAL,


   -- SAE J3161 vehicle-density value for the producer-defined relevant range.
   --
   j3161VehicleDensityInRange           INTEGER (0..65535)   OPTIONAL,

   ...
}

END
