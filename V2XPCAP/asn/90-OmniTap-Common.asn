-- OmniTap common types.
-- Normative: OmniTap uses ASN.1 COER (ITU-T X.696) for every OmniTap object.
-- Normative: PEN 32473 is the RFC 5612 documentation PEN and is a placeholder. Every OmniTap module OID SHALL be
-- rebased onto the IANA PEN assigned to the final profile owner before publication; see 00-OmniTap-Registrations.md.
OmniTap-Common { 1 3 6 1 4 1 32473 omniTap(1) common(90) major-version-1(1) minor-version-0(0) }
DEFINITIONS AUTOMATIC TAGS ::= BEGIN
EXPORTS ALL;

-- Provenance of the numeric widths in this module. OmniTap did not choose the large ranges below; most are fixed by other
-- specifications, and the rest are marked as OmniTap's own choices:
--     CaptureSessionId     128 bits  A UUID (RFC 9562).
--     SessionTag           32 bits   High half of the 64-bit epb_packetid option of the pcapng Enhanced Packet Block.
--     RecordId             32 bits   Low half of that option (IETF OPSAWG pcapng specification, section 4.3).
--     PEN fields           32 bits   Private Enterprise Number field of a pcapng Custom Block (section 4.8). The
--                                    Supplemental Result and Extensions modules use the same width.
--     PcapngInterfaceName  1..255    OmniTap's own limit. pcapng gives every option a 16-bit length field.
--     ElapsedTimeUs        32 bits   OmniTap's own choice. pcapng defines no such duration.
-- The split of epb_packetid into SessionTag and RecordId is also OmniTap's own; pcapng defines only the 64-bit value.

-- Normative: 128-bit producer-assigned capture-session identity. A new value SHALL be used for each capture session
-- and reused across all pcapng sections and files of that session. UUIDv7 is recommended.
CaptureSessionId ::= OCTET STRING (SIZE(16))

-- Normative: epb_packetid layout. The pcapng epb_packetid option (Wireshark: frame.packet_id) is one 64-bit number on an
-- EPB. OmniTap splits it into two 32-bit halves:
--     epb_packetid = SessionTag * 2^32 + RecordId
--     bits 63..32 = SessionTag (high half: which capture session)
--     bits 31..0  = RecordId   (low half: which packet within that session)
-- Why split: two captures may both number packets from 1. After mergecap or similar tools combine them, RecordId alone
-- is ambiguous; the SessionTag keeps the packets distinct. A 32-bit RecordId allows 4294967296 packets per session
-- (about 24 days at 2000 packets per second); sessions SHOULD be restarted before they exceed that.
-- Normative: SessionTag is the last four octets of the CaptureSessionId, read as an unsigned big-endian integer.
-- Why the last octets: in a UUIDv7 the first octets are a timestamp, so sessions started close together share them.
-- Example: a CaptureSessionId ending 7C 11 5E 90 gives SessionTag 0x7C115E90 (2081513104 decimal).
SessionTag ::= INTEGER (0..4294967295)

-- Normative: Producer-assigned 32-bit number of one logical packet within its capture session, for example 1, 2, 3, ...
-- It is the LOW 32 bits of the associated EPB's epb_packetid option (see SessionTag for the layout). Packet Metadata and
-- Supplemental Result carry the same value, which is how they find their packet.
-- Example: SessionTag 0x7C115E90 and RecordId 5 give epb_packetid 0x7C115E9000000005.
-- (SessionTag, RecordId) identifies one logical packet across merged captures; the full CaptureSessionId resolves the
-- rare case of two sessions sharing a SessionTag (about 1 in 4294967296 per pair of sessions).
RecordId ::= INTEGER (0..4294967295)

-- Normative: The if_name option of an IDB. Producers SHOULD give each IDB an if_name that is unique within the capture
-- session; (SessionTag, PcapngInterfaceName) identifies an interface across merged captures. Producers SHALL write
-- if_name on every IDB of an interface that has Interface Context.
PcapngInterfaceName ::= UTF8String (SIZE(1..255))

-- Normative: Duration in microseconds; zero means coincidence with the applicable EPB timestamp. The maximum value
-- 4294967295 (about 71.6 minutes) means that duration or longer.
ElapsedTimeUs ::= INTEGER (0..4294967295)

V2XTechnology ::= ENUMERATED {
   lteV2x      (0),   -- 3GPP LTE PC5 sidelink (V2X and Release 18+ A2X).

   nrV2x       (1),   -- 3GPP NR PC5 sidelink (V2X and Release 18+ A2X).

   -- IEEE 802.11p radio access outside the context of a BSS, as profiled by ETSI EN 302 663 (ITS-G5). Native EPB
   -- packet bytes begin with a standard Radiotap header.
   --
   etsiItsG5   (2),


   -- ITS Connect, the Japanese V2X system: the ARIB STD-T109 700 MHz band ITS radio (single 760 MHz channel) plus the
   -- ITS FORUM RC-010 extended layer.
   --
   aribT109    (3),

   ...
}

PayloadDescriptor ::= SEQUENCE {
   payloadKind     PayloadKind,                -- Normative: Classifies the unmodified packet data in the associated EPB.

   nonIpFamilyId   NonIpFamilyId   OPTIONAL,   -- Present only when payloadKind is nonIp and family is known.

   ...
}

PayloadKind ::= ENUMERATED {
   ip      (0),   -- Native EPB packet data begins with an IP packet.

   nonIp   (1),   -- Native EPB packet data belongs to a non-IP protocol family.

   ...
}

-- Normative: Assigned values mirror 3GPP TS 24.386; reserved preserves its assigned value.
NonIpFamilyId ::= ENUMERATED {
   reserved    (0),   -- Reserved by 3GPP TS 24.386.

   ieee1609    (1),   -- IEEE 1609 family, including WSMP and WSA payloads.

   iso29281    (2),   -- ISO 29281-1 family.

   etsiIts     (3),   -- ETSI ITS family.

   chinaDsmp   (4),   -- China DSMP family.

   ...
}

END
