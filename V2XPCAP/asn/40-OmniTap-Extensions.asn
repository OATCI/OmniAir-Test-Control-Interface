-- OmniTap optional extension containers: regional and third-party (PEN-owned).
-- Normative: A base-profile reader SHALL NOT interpret opaqueValue. It MAY retain, display, or pass it to an owner-specific
-- decoder. Third-party content may include manufacturer-private capabilities, proprietary diagnostics, calibration data,
-- or tool-specific annotations. Extension types are locally scoped, never globally unique.
OmniTap-Extensions { 1 3 6 1 4 1 32473 omniTap(1) extensions(40) major-version-1(1) minor-version-0(0) }
DEFINITIONS AUTOMATIC TAGS ::= BEGIN
EXPORTS ALL;

-- Normative: Every OmniTap object that has extension space carries this type in a field named optionalExtensions. It holds
-- up to two regional and up to two PEN-owned extension values.
OptionalExtensions ::= SEQUENCE {

   -- Zero, one, or two regional extension values applicable to enclosing object.
   --
   regionalExtensions     SEQUENCE (SIZE(1..2)) OF RegionalExtension     OPTIONAL,


      -- Zero, one, or two PEN-owned extension values applicable to the enclosing object (for example, manufacturer-private
   -- capabilities, proprietary diagnostics, calibration data, or tool-specific annotations).
   --
   thirdPartyExtensions   SEQUENCE (SIZE(1..2)) OF ThirdPartyExtension   OPTIONAL,

   ...
}

RegionalExtension ::= SEQUENCE {
   regionalIdentifier   OCTET STRING (SIZE(1..32)),   -- Identifies the regional extension namespace.

   -- Type identifier scoped only by regionalIdentifier; values may be reused by other regions.
   --
   extensionType        INTEGER (0..255),


   -- Owner-defined payload; owner defines its internal encoding and versioning, if any.
   --
   opaqueValue          OCTET STRING (SIZE(1..2048)),

   ...
}

-- Carries one PEN-owned extension, such as manufacturer-private capabilities or proprietary diagnostic information.
--
ThirdPartyExtension ::= SEQUENCE {
   ownerPen        INTEGER (0..4294967295),   -- IANA PEN identifying the third-party extension owner.

   -- Type identifier scoped only by ownerPen; values may be reused by other owners.
   --
   extensionType   INTEGER (0..255),


   -- Owner-defined payload; owner defines its internal encoding and versioning, if any.
   --
   opaqueValue     OCTET STRING (SIZE(1..2048)),

   ...
}

END
