V2X-Pcapng-Record
{ iso(1) identified-organization(3) v2x-pcapng-profile(99999) record(0) version1(1) }
DEFINITIONS AUTOMATIC TAGS ::= BEGIN
IMPORTS V2XCommonMetadata, OpaqueData FROM V2X-Pcapng-Common
        TechnologySpecificMetadata FROM V2X-Pcapng-Radio
        AnalysisAnnotations FROM V2X-Pcapng-Annotations;

-- This object is encoded as the profile-defined V2X per-packet pcapng option, or as a correlated metadata block.
-- It is not inserted into the native packet data. For DSRC native packet data remains Radiotap -> IEEE 802.11/WAVE.
V2XPcapngPacketMetadata ::= SEQUENCE {
  common                   V2XCommonMetadata,
  technologySpecific       TechnologySpecificMetadata OPTIONAL,
  analysis                 AnalysisAnnotations OPTIONAL,
  nativePacketDigest       OCTET STRING OPTIONAL,
  ...
}
END
