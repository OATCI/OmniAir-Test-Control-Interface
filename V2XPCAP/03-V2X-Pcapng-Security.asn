V2X-Pcapng-Security
{ iso(1) identified-organization(3) v2x-pcapng-profile(99999) security(3) version1(1) }
DEFINITIONS AUTOMATIC TAGS ::= BEGIN
IMPORTS ProcessingResult, RegionalExtension, ManufacturerExtension FROM V2X-Pcapng-Common;

-- Security validation is one annotation. Relevance and consistency are security-validation subcategories.
SecurityValidationAnnotation ::= SEQUENCE {
  attempted                BOOLEAN,
  processed                BOOLEAN,
  overallResult            ProcessingResult,
  cryptographic            ProcessingStatus OPTIONAL,
  credential               ProcessingStatus OPTIONAL,
  relevance                ProcessingStatus OPTIONAL,
  consistency              ProcessingStatus OPTIONAL,
  failureFlags             SecurityFailureFlags OPTIONAL,
  regionalExtensions       SEQUENCE OF RegionalExtension OPTIONAL,
  manufacturerExtensions   SEQUENCE OF ManufacturerExtension OPTIONAL,
  ...
}
ProcessingStatus ::= SEQUENCE { attempted BOOLEAN, processed BOOLEAN, result ProcessingResult, ... }
SecurityFailureFlags ::= BIT STRING {
  parseFailure(0), unsupportedCriticalInformation(1), signatureFailure(2), signerNotFound(3),
  certificateNotYetValid(4), certificateExpired(5), certificateRevoked(6), chainFailure(7),
  untrustedRoot(8), revocationInformationUnavailable(9), unauthorizedService(10),
  generationTimeTooOld(11), generationTimeFuture(12), expiryTimeExpired(13),
  invalidValidityRegion(14), duplicateOrReplay(15), timeInconsistency(16),
  permissionInconsistency(17), otherConsistencyFailure(18)
}
END
