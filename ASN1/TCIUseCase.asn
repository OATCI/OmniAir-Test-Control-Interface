/* Copyright OmniAir Consortium Inc. All rights reserved.
   Licensed http://www.apache.org/licenses/LICENSE-2.0 (the "License");
   You may not use this file except in compliance with the License.  */

/* Module: TCI-UseCase
   Purpose:  This TCI module includes control messages for configuring/disable/enable the
   UCAM (Use Case Announcement Message) which tells test equipment and/or broadcasts the vehicle
   safety applications "alert state" (new warning triggered, old warning cleared, or preempted)

   This TCI module allows Test Equipment (TE) to reconfgure the safety system under test (e.g. V2X OBU) to 
   keep the UCAM production enabled for X hours (across reboots), and where/how to send the 
   UCAM results (e.g. TCI response,  UDP over ethernet, TCP over ethernet, DSMP broadcast, ETSI ITS BTP , WSMP
   over the air.
   
   
*/



TCI-UseCase

DEFINITIONS AUTOMATIC TAGS ::=
BEGIN

IMPORTS
Response,
Exception,
Time64,
MsgID FROM TCI-CommonTypes


SetInitialState FROM TCI-wsm

;

TCIUseCase ::= CHOICE{
    request         [0] Request,
    response        [1] Response,
    announcement    [2] UTF8String (SIZE(10..1445)),  -- JSON JER UCAM limited by 1500b TS/SUT UDP MTU
                                                      -- When UCAM JER exceeds MTU, split into multiple TCI UCAM "announcements"
    exception       [4] Exception,
    ...
}

Request ::=  SEQUENCE {
    messageId   MESSAGE-ID-AND-TYPE.&id({MessageTypes}),
    value       MESSAGE-ID-AND-TYPE.&Type({MessageTypes}{@.messageId}),
    ...
}

MESSAGE-ID-AND-TYPE ::= CLASS {
    &id    MsgID UNIQUE,
    &Type
} WITH SYNTAX {&Type IDENTIFIED BY &id}

MessageTypes MESSAGE-ID-AND-TYPE ::= {
    { SetInitialState IDENTIFIED BY setInitialState} |
    { SetUseCaseAnnouncementConfig IDENTIFIED BY setUseCaseAnnouncementConfig }

}

setInitialState                     MsgID ::= 1
setUseCaseAnnouncementConfig        MsgID ::= 2


-- Use Case Announcement(UCAM) configuration TCI command.
-- configure the SUT to send/transmit Usecase Announcements to the specified destination.
-- Default behavior if enabled is to send over TCI Response, but can also be sent via UDP, TCP, WSMP, GN, DSMP
SetUseCaseAnnouncementConfig ::= SEQUENCE {
   enableUcamMinutes	     INTEGER(0..3000), -- set to 0 to disable, persistent in SUT. SUT  automatically disables after this.
   repeatRateMillseconds  INTEGER(0..10000) OPTIONAL, -- if alert ongoing, how often to UCAM; 0 disables Default value is 500ms (2Hz)
   setSystemName          UTF8String (SIZE(1..8)) OPTIONAL,  -- Friendly SUT name, used in UCAM.  no default,if not set, UCAM "nam" is empty
   heartbeatSeconds	     INTEGER(0..300) OPTIONAL, -- even if no alerts, if UcamEnabled, UCAM heartbeat at least often (no alerts). Default=1 sec

   -- Optional , though generally default delivery of UCAM to the TE, (Typically over TCI, but can be UDP or TCP
   wiredUcamDelivery       UcamNetworkType,                      --TCI UCAM's, disabled or TCP/UDP over Wi-Fi/Ethernet, etc.
   wiredDestination        WiredNetworkDestination OPTIONAL,     --Excluded if wiredUcamDelivery is disabled or TCI

   -- Wireless over the air (OTA) broadcast destination.  Can be instead or in conjunction with wiredDestination.
   wirelessBroadcastEnable   BOOLEAN,
   wirelessBroadcast         WirelessBroadcastConfig OPTIONAL,   --Excluded if wirelessBroadcastEnable is false
   ...
}
(
  (WITH COMPONENTS {..., wiredUcamDelivery( netDisable | netTci ), wiredDestination ABSENT})
 |(WITH COMPONENTS {..., wiredUcamDelivery( netUdp | netTcp ), wiredDestination PRESENT})
 |(WITH COMPONENTS {..., wirelessBroadcastEnable( FALSE ), wirelessBroadcast ABSENT})
 |(WITH COMPONENTS {..., wirelessBroadcastEnable( TRUE ), wirelessBroadcast PRESENT})
)

-- other transports have various other value.
UcamNetworkType ::= ENUMERATED {
   netDisable      (0), -- Disabled, no UCAM sent over TCI/Ethernet/Wi-Fi
   netTci          (1), -- UCAM sent encapsulated in  TCI announcement
   netUdp          (2), -- sent as Raw JSON UDP payload to UDP4 or UDP6 destination/port
   netTcp          (3), -- connect to spcified TCP server, and send UCAM's over TCP
   ...
}

-- how is the UCAM on the radio interface(e.g. field testing , with RSU sniffers)
UcamTransportType ::= ENUMERATED {
   transportRaw    (0), -- UCAM JSON dumped into the interface with no headers, no WSMP.
   transportWsmp   (1), -- 1609 headers added, using PSID configured in SetUseCaseAnnouncementConfig
   transportDsmp   (2), -- China DSMP headers added, using PSID configured in SetUseCaseAnnouncementConfig
   transportBtp    (3), -- ETSI ITS send in GN+BTP as indicated
   broadcastUdp    (4), -- UDP 6 or 4 per  address type SetUseCaseAnnouncementConfig
   ...
}

WiredNetworkDestination ::= SEQUENCE {
   -- non TCI TCP or UDP  Network delivery config of UCAM (Could be IPv6 or IPv4 of any network interface except CV2X)

   wiredDestIpAddressString    UTF8String (SIZE(1..40)) OPTIONAL, -- IPV4 or IPV6, without port#
   wiredIpDestPort INTEGER(0..65535) OPTIONAL,                    -- UDP/TCP if not just sending over TCI 
   ...
}

WirelessBroadcastConfig ::= SEQUENCE {
   -- optional related to broadcasting OTA
   otaTransport            UcamTransportType ,                -- how to broadcast the UCAM OTA
   otaPsidValue            INTEGER(0..300000000) OPTIONAL,    -- PSID/AID to send OTA with, if enabled.
   otaSecured              BOOLEAN OPTIONAL,                  -- WSMp/DSMP signed with certs enabling otaPsidValue, not relevant to UDP
   otaDestIpAddressString  UTF8String (SIZE(1..40)) OPTIONAL, -- IPV4 or IPV6, without port#
   otaIpDestPort           INTEGER(0..65535) OPTIONAL,        -- For UDP4/UDP6 if not broadcasting over WSMP/BTP/DSMP
   ...
}


END
