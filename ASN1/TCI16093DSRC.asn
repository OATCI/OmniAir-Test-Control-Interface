--OSS.PDU TCI-16093.TSI16093Event>--
TCI-16093-DSRC
DEFINITIONS AUTOMATIC TAGS ::=
BEGIN

IMPORTS
dsrcMtu,
Exception,
Response,
MsgID FROM TCI-CommonTypes

SetInitialState,
SetWsmTxInfo,
StartWsmTx,
StopWsmTx,
StartWsmRx,
StopWsmRx,
StartWsaTxPerdiodic,
StopWsaTxPeriodic,
AddWsaProviderService,
ChangeWsaProviderService,
DelWsaProviderService,
AddUserService,
DelUserService FROM TCI-wsm

GetIPv6InterfaceInfo,
SetIPv6Address,
StartIPv6Ping,
StopIPv6Ping FROM TCI-ip

ResponseInfo FROM TCI-responseInfo

Indication FROM TCI-indication

;

TCI16093DSRC ::= CHOICE{
    request         [0] Request,
    response        [1] Response,
    indication      [2] Dot3Indication,
    responseInfo    [3] Dot3ResponseInfo,
    exception       [4] Exception,
    ...
    }

Request ::=  SEQUENCE {
   messageId   MESSAGE-ID-AND-TYPE.&id({MessageTypes}),
   value       MESSAGE-ID-AND-TYPE.&Type({MessageTypes}{@.messageId}),
   ...
   }

MESSAGE-ID-AND-TYPE ::= CLASS {
   &id    MsgID UNIQUE,
   &Type
   } WITH SYNTAX {&Type IDENTIFIED BY &id}

MessageTypes MESSAGE-ID-AND-TYPE ::= {
-- imported from TCI-wsm module
    { SetInitialState   IDENTIFIED BY setInitialState } |
    { Dot3SetWsmTxInfo IDENTIFIED BY setWsmTxInfo} |
    { Dot3StartWsmTx IDENTIFIED BY startWsmTx} |
    { StopWsmTx IDENTIFIED BY stopWsmTx} |
    { Dot3StartWsaTxPerdiodic IDENTIFIED BY startWsaTxPerdiodic} |
    { StopWsaTxPeriodic IDENTIFIED BY stopWsaTxPeriodic} |
    { Dot3StartWsmRx IDENTIFIED BY startWsmRx} |
    { StopWsmRx IDENTIFIED BY stopWsmRx} |
    { AddWsaProviderService IDENTIFIED BY addWsaProviderService} |
    { ChangeWsaProviderService IDENTIFIED BY changeWsaProviderService} |
    { DelWsaProviderService IDENTIFIED BY delWsaProviderService} |
    { AddUserService IDENTIFIED BY addUserService} |
    { DelUserService IDENTIFIED BY delUserService} |
-- imported from TCI-ip module
    { GetIPv6InterfaceInfo IDENTIFIED BY getIpv6InterfaceInfo} |
    { SetIPv6Address IDENTIFIED BY setIpv6Address} |
    { StartIPv6Ping IDENTIFIED BY startIpv6Ping} |
    { StopIPv6Ping IDENTIFIED BY stopIpv6Ping}
}

setInitialState                         MsgID ::= 1
setWsmTxInfo                            MsgID ::= 2
startWsmTx                              MsgID ::= 3
stopWsmTx                               MsgID ::= 4
startWsaTxPerdiodic                     MsgID ::= 5
stopWsaTxPeriodic                       MsgID ::= 6
startWsmRx                              MsgID ::= 7
stopWsmRx                               MsgID ::= 8
addWsaProviderService                   MsgID ::= 9
changeWsaProviderService                MsgID ::= 10
delWsaProviderService                   MsgID ::= 11
addUserService                          MsgID ::= 12
delUserService                          MsgID ::= 13
getIpv6InterfaceInfo                    MsgID ::= 14
setIpv6Address                          MsgID ::= 15
startIpv6Ping                           MsgID ::= 16
stopIpv6Ping                            MsgID ::= 17

/*
    Request Messages

    SetInitialState,
    SetWsmTxInfo,
    StartWsmTx,
    StopWsmTx,
    StartWsmRx,
    StopWsmRx,
    StartWsaTxPerdiodic,
    StopWsaTxPeriodic,
    AddWsaProviderService,
    ChangeWsaProviderService,
    DelWsaProviderService,
    AddUserService,
    DelUserService FROM TCI-wsm
*/


Dot3SetWsmTxInfo ::= SetWsmTxInfo (WITH COMPONENTS {
    psid,
    radio,
    security,
    transmitPowerLevel,
    infoElementsIncluded,
    userPriority,
    channelIdentifier,
    dataRate,
    timeslot,
    repeatRate ABSENT,
    destinationMACAddr ('FFFFFFFFFFFF'H),
    channelLoad ABSENT,
    expiryTime  ABSENT,
    payload ABSENT,
--	txPoolId ABSENT,
	flowId ABSENT
})

Dot3StartWsmTx ::= StartWsmTx (WITH COMPONENTS {
    psid,
    radio,
    repeatRate,
    payload(SIZE(0..dsrcMtu)) PRESENT
})

Dot3StartWsmRx ::= StartWsmRx (WITH COMPONENTS {
    psid OPTIONAL,
    radio,
    channelIdentifier,
    timeSlot,
    eventHandling,
	destinationMACAddr OPTIONAL,
    pduFilter OPTIONAL
})


Dot3StartWsaTxPerdiodic ::= StartWsaTxPerdiodic (WITH COMPONENTS {
    radio,
    destinationMACAddr ('FFFFFFFFFFFF'H),
    wsaChannelIdentifier,
    channelAccess,
    repeatRate,
    ipService,
    security,
    signatureLifetime,
    infoElementIncluded,
    advertiserId OPTIONAL,
    serviceInfos,
    channelinfos,
    wra OPTIONAL,
    -- if the following parameters omitted, use the default values from the SUT MIB
    dataRate OPTIONAL,
    userPriority OPTIONAL,
    transmitPowerLevel OPTIONAL,
    headerExts OPTIONAL,
    flowId ABSENT
})

/*
   Indication Messages
*/

Dot3Indication ::= Indication (WITH COMPONENTS {
    radio,
    event ( e16093PktRx |
            eWsmPktRx |
            eIpv6PktRx |
            eIcmp6PktRx |
            eIpv6ConfigChanged |
            eDot3ChannelAssigned |
            eDot3RequestMatchedAvailAppService |
            eDot2VerificationCompleteWithResult |
            exception),
    eventParams (WITH COMPONENTS {service} |
                 WITH COMPONENTS {wsm} |
                 WITH COMPONENTS {ip} |
                 WITH COMPONENTS {security}
                 ) OPTIONAL,
    pdu OPTIONAL,
    exception OPTIONAL
    })

/*
   ResponseInfo Messages
*/

Dot3ResponseInfo ::= ResponseInfo (WITH COMPONENTS {
    msgID,
    resultCode,
    info (WITH COMPONENTS {ipv6InterfaceInfo} |
          WITH COMPONENTS {sutInfo} |
          WITH COMPONENTS {pktCount}  ) OPTIONAL, -- if exception reported, no InfoContent provided
    exception OPTIONAL
    })

END
