TCI-80211
DEFINITIONS AUTOMATIC TAGS ::=
BEGIN

IMPORTS
dsrcMtu,
Response,
Exception,
MsgID FROM TCI-CommonTypes

SetInitialState,
SetWsmTxInfo,
StartWsmTx,
StopWsmTx,
StartWsmRx,
StopWsmRx  FROM TCI-wsm

Indication FROM TCI-indication
;

TCI80211 ::= CHOICE{
    request         [0] Request,
    response        [1] Response,
    indication      [2] Dot11Indication,
--  responseInfo    [3] Dot11ResponseInfo,
    exception       [4] Exception,
    ...
    }

Request ::=  SEQUENCE {
   messageId   MESSAGE-ID-AND-TYPE.&id({MessageTypes}),
   value       MESSAGE-ID-AND-TYPE.&Type({MessageTypes}{@.messageId}),
   ...
   }


MESSAGE-ID-AND-TYPE ::= CLASS {
   &id    MsgID UNIQUE,
   &Type
   } WITH SYNTAX {&Type IDENTIFIED BY &id}


MessageTypes MESSAGE-ID-AND-TYPE ::= {
-- imported from TCI-wsm
    { SetInitialState IDENTIFIED BY setInitialState} |
    { Dot11SetWsmTxInfo IDENTIFIED BY setWsmTxInfo} |
    { Dot11StartWsmTx IDENTIFIED BY startWsmTx} |
    { StopWsmTx IDENTIFIED BY stopWsmTx} |
    { StartWsmRx IDENTIFIED BY startWsmRx} |
    { StopWsmRx IDENTIFIED BY stopWsmRx}
}

setInitialState         MsgID ::= 1
setWsmTxInfo            MsgID ::= 2
startWsmTx              MsgID ::= 3
stopWsmTx               MsgID ::= 4
startWsmRx              MsgID ::= 5
stopWsmRx               MsgID ::= 6

/*
    Request Messages

    SetInitialState,
    SetWsmTxInfo,
    StartWsmTx,
    StopWsmTx,
    StartWsmRx,
    StopWsmRx FROM TCI-wsm

*/

Dot11SetWsmTxInfo ::= SetWsmTxInfo (WITH COMPONENTS {
    psid,
    radio,
    security,
    transmitPowerLevel,
    infoElementsIncluded,
    userPriority,
    channelIdentifier,
    dataRate,
    timeslot,
    repeatRate ABSENT,
    destinationMACAddr ('FFFFFFFFFFFF'H),
    channelLoad ABSENT,
    expiryTime  ABSENT,
    payload ABSENT
})

Dot11StartWsmTx ::= StartWsmTx (WITH COMPONENTS {
    psid,
    radio,
    repeatRate,
    payload(SIZE(0..dsrcMtu)) PRESENT
})

Dot11Indication ::= Indication (WITH COMPONENTS {
    radio,
    event (eRadioPktRx),
    eventParams (WITH COMPONENTS {radioframe} ) OPTIONAL,
    pdu OPTIONAL,
    exception OPTIONAL
    })

END
